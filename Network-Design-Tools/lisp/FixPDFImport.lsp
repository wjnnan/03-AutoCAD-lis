; Written by Alex McTeague
(defun c:FixPDFImport ( / txtSet hatchSet enameCase objCase minPt maxPt pt1 pt2 ptCase echo i caseCt enameTxt j entTxt str strPre strPost startPt rot textHeight scale dist endPt len)  
  (print "Select entire import")
  (setq txtSet (ssget '((0 . "*TEXT") (8 . "PDF*_Text"))))
  (if (null txtSet)
    (progn
      (princ "\nNo text objects found -- aborting.")
      (quit)
    )
  )
  
  (print "Select splice case symbol")
  (setq hatchSet (ssget '((0 . "HATCH"))))
  (if (null hatchSet)
    (progn
      (princ "\nNo HATCH objects found -- aborting.")
      (quit)
    )
  )
  (setq enameCase (ssname hatchSet 0))
  (setq objCase (vlax-ename->vla-object enameCase))
  (if (vl-catch-all-error-p
        (vl-catch-all-apply 'vla-getboundingbox (list objCase 'minPt 'maxPt)))
    (progn (princ "
错误: 无法获取边界框。") (quit)))
  (setq pt1 (vlax-safeArray->list minPt))
  (setq pt2 (vlax-safeArray->list maxPt))
  (setq ptCase (mapcar '(lambda (x1 x2) (/ (+ x1 x2) 2.0)) pt1 pt2))
  
  (setq echo (getvar 'cmdecho))
  (setvar 'cmdecho 0)
  
  (command "_LAYER" "SET" "F-102_PASSIVES" "")
  (command "_COLOR" "BYLAYER")
  
  (setq i 0)
  (setq caseCt 0)
  (while (setq enameTxt (ssname txtSet i))
    (setq j 6)
    (setq entTxt (entget enameTxt))
    (setq str (cdr (assoc 1 entTxt)))
    (setq strPre (substr str 1 j))
    (setq strPost (substr str (+ j 1) (strlen str)))
    (cond
      ((wcmatch str "SP####`.*")
        (progn
          (command "_JUSTIFYTEXT" enameTxt "" "MC")
          (setq entTxt (entget enameTxt))
          (setq startPt (cdr (assoc 10 entTxt)))
          (setq rot (- (cdr (assoc 50 entTxt)) (/ pi 2)))
          (setq textHeight (cdr (assoc 40 entTxt)))
          (setq scale (/ textHeight 25.00))
          (setq dist (* textHeight 2.043))
          (setq endPt (list (+ (car startPt) (* dist (cos rot))) (+ (cadr startPt) (* dist (sin rot)))))
          (command "_COPY" enameCase "" ptCase endPt)
          (command "_ROTATE" (entlast) "" endPt (+ (* 180.0 (/ rot pi)) 90))
          (command "_SCALE" (entlast) "" endPt scale)
          (setq caseCt (+ caseCt 1))
        )
      )
      ((wcmatch strPost (strcat "*" strPre "*"))
        (if (not (wcmatch strPre "GR-*"))
          (progn
            (setq len (strlen str))
            (while (<= j len)
              (setq strPre (substr str 1 j))
              (setq strPost (substr str (- len (- j 1)) len))
              (if (= strPre strPost)
                (setq j 1000)
              )
              (setq j (+ j 1))
            )
            (setq entTxt (subst (cons 1 strPre) (assoc 1 entTxt) entTxt))
            (entmod entTxt)
            (princ (strcat "\n* Trimmed '" str "' ---> '" strPre "'\n"))
          )
        )
      )
    )
    (setq i (+ i 1))
  )
  
  (princ (strcat "\nPlaced " (itoa caseCt) " splice cases"))
  (princ "\nFinished fixing PDF Import")
  (setvar 'cmdecho echo)
  (princ)
)
