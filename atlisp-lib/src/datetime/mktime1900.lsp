(defun datetime:mktime1900 (timestamp)
  "unix timestamp 转 到1900年01月01日经过的秒数."
  "real"
  "(datetime:mktime1900 (datetime:mktime (vl-file-systime (findfile \"acad.pgp\"))))"
  (+ (* 22089.0 100000.0)
    88800.0 timestamp))
