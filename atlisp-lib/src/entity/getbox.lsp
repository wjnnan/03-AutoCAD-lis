(defun entity:getbox (ent offset / lst obj p1 p2 p3 p4)
  "图元的最小包围盒"
  "return:外框（偏移后）的左下，右上角点"
  "example:(entity:getbox (car(entsel))
    0.1)"
  (if (= (quote pickset)
	 (type ent))
      (pickset:getbox ent offset)
    (progn (setq obj (vlax-ename->vla-object ent))
      (if (vl-catch-all-error-p
            (vl-catch-all-apply 'vla-getboundingbox (list obj (quote p1) (quote p3))))
        (setq p1 nil p3 nil))
      (setq p1 (vlax-safearray->list p1)
        p3 (vlax-safearray->list p3))
      (if (= "SPLINE"
          (cdr (assoc 0 (entget ent))))
        (progn (setq lst (mapcar (quote (lambda (a b)
                  (vlax-curve-getclosestpointtoprojection ent a b t)))
              (list p1 (list (car p1)
                  (cadr p3)
                  (caddr p1))
                p3 (list (car p3)
                  (cadr p1)
                  (caddr p1)))
              (quote ((1.0 0 0)
                  (0 -1.0 0)
                  (-1.0 0 0)
                  (0 1.0 0)))))
          (setq p1 (apply (quote mapcar)
              (cons (quote min)
                lst))
            p3 (apply (quote mapcar)
              (cons (quote max)
                lst)))))
      (if (or (not offset)
          (equal offset 0 0.0001))
        (list p1 p3)
        (list (list:- p1 (list offset offset 0))
          (list:+ p3 (list offset offset 0)))))))
