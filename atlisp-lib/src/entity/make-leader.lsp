(defun entity:make-leader (startpt endpt)
  "创建无标记的箭头标注"
  (entmake (list (quote (0 . "leader"))
      (quote (100 . "AcDbEntity"))
      (quote (100 . "AcDbLeader"))
      (quote (71 . 1))
      (quote (72 . 0))
      (quote (73 . 3))
      (quote (74 . 1))
      (quote (75 . 0))
      (quote (40 . 0.0))
      (quote (41 . 0.0))
      (quote (76 . 2))
      (cons 10 startpt)
      (cons 10 endpt)
      (quote (211 1.0 0.0 0.0))
      (quote (210 0.0 0.0 1.0))
      (quote (212 0.0 0.0 0.0))
      (quote (213 0.0 0.0 0.0)))))
