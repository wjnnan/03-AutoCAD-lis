(defun entity:reference->definition (ent / a n xs ys zs)
  "计算块参照与块定义的变换矩阵"
  "返 回 值:3x3矩阵和向量组成的表"
  "示    例:(entity:Reference->Definition e)"
  (setq a (vla-get-rotation e)
    n (vla:getvalue (vla-get-normal e))
    xs (max (abs (vla-get-xscalefactor e)) 1e-12)
    ys (max (abs (vla-get-yscalefactor e)) 1e-12)
    zs (max (abs (vla-get-zscalefactor e)) 1e-12))
  ((lambda (m)
      (list m (mapcar (quote -)
          (vla:-getvalue (vla-get-origin (vla-item (vla-get-blocks *doc*)
                (vla-get-name e))))
          (matrix:mxv m (trans (vla:-getvalue (vla-get-insertionpoint e))
              n 0)))))
    (matrix:mxm (list (list (/ 1.0 xs)
          0.0 0.0)
        (list 0.0 (/ 1.0 ys)
          0.0)
        (list 0.0 0.0 (/ 1.0 zs)))
      (matrix:mxm (list (list (cos a)
            (sin (- a))
            0.0)
          (list (sin a)
            (cos a)
            0.0)
          (list 0.0 0.0 1.0))
        (mapcar (quote (lambda (e)
              (trans e n 0 t)))
          (quote ((1.0 0.0 0.0)
              (0.0 1.0 0.0)
              (0.0 0.0 1.0))))))))
