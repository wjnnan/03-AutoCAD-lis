(defun entity:make-pline (plist convexity elevation closed)
  "生成二维多段线.POLYLINE\n参数:\n  plist:端点坐标点表，如：((x1 y1 z1)
    (x2 y2 z2)
    (x2 y2 z2))或((x1 y1)
    (x2 y2)
    (x2 y2))\n  convexity:各点与下一点的凸度(个数同坐标点表)，可为nil\n  elevation:标高\n  closed:是否闭合，1:闭合，0：不闭合"
  "返回值:  生成多段线的图元名"
  "示例:  (entity:make-pline '((0 0 0)
      (5000 0 0)
      (5000 5000 0)
      (0 5000 0))
    '(-1.0 -0.5 0 -0.3)
    100 1)"
  (if (= closed 1)
    (entmake (list (quote (0 . "POLYLINE"))
        (quote (100 . "AcDbEntity"))
        (quote (67 . 0))
        (quote (410 . "Model"))
        (quote (8 . "0"))
        (quote (100 . "AcDb3dPolyline"))
        (quote (66 . 1))
        (quote (10 0.0 0.0 0.0))
        (quote (70 . 16))
        (quote (40 . 0.0))
        (quote (41 . 0.0))
        (quote (210 0.0 0.0 1.0))
        (quote (71 . 0))
        (quote (72 . 0))
        (quote (73 . 0))
        (quote (74 . 0))
        (quote (75 . 0))))
    (entmake (list (quote (0 . "POLYLINE"))
        (quote (66 . 1)))))
  (if convexity (mapcar (quote (lambda (x y)
          (entmake (list (cons 0 "VERTEX")
              (cons 10 x)
              (cons 42 y)))))
      plist convexity)
    (mapcar (quote (lambda (x)
          (entmake (list (cons 0 "VERTEX")
              (cons 10 x)))))
      plist))
  (entmake (quote ((0 . "SEQEND"))))
  (entlast))
