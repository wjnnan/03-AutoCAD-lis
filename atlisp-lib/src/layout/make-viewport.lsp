(defun layout:make-viewport (layout pt-center width height twistang pt-model / obj-pv)
  "从模型空间生成布局"
  "ename"
  (if (null (member layout (layout:list)))
      (progn
	(vla-add *layouts* layout)
	(if (/= layout (getvar "ctab"))(setvar "ctab" layout))
	(pickset:erase (ssget "x" (list (cons 410 layout))))
	)
      (if (/= layout (getvar "ctab"))(setvar "ctab" layout)))
  (if (null twistang)
      (setq twistang 0.0)
    (if (not (zerop twistang))
	(setq pt-model
	      (m:coordinate-rotate pt-model  twistang)
	      )))
  (if (/= layout (getvar "ctab"))(setvar "ctab" layout))
  (setvar "cmdecho" 0)
  (@::cmd "mview"
	  "NE"
	  (polar (polar pt-model pi (* 0.5 width))
		 (* 1.5 pi)
		 (* 0.5 height))
	  (polar (polar pt-model 0 (* 0.5 width))
		 (* 0.5 pi)
		 (* 0.5 height))
	  ""
	  pt-center)
  (setvar "cmdecho" 1)
  ;;调整比例
  (setq obj-pv (e2o (entlast)))
  (vla-put-width obj-pv width)
  (vla-put-height obj-pv height)
  (vla-put-customscale obj-pv 1.0)
  (vla-put-twistangle obj-pv twistang)
  (o2e obj-pv)
  )

;; (if (member layout (layout:list))
;;       (progn (setvar "ctab" layout)
;; 	     (vla-put-activespace *doc* acpaperspace)
;; 	     (setq obj-layout (nth (vl-position layout (layout:list))
;; 				   (layout:vla-list)))
;; 	     (setq obj-pv (vla-addpviewport (setq paperspace (vla-get-paperspace *doc*))
;; 					    (point:to-ax pt-center)
;; 					    width height))
;; 	     ;; (vla-display obj-pv :vlax-true)
;; 	     ;; (vla-update  obj-pv)
;; 	     ;; 模型基点
;; 	     (vla-getxdata obj-pv "ACAD" 'mtypes 'mvalues)
;; 	     (vlax-safearray-put-element
;; 	      mvalues 8 (car pt-model))
;; 	     (vlax-safearray-put-element
;; 	      mvalues 9 (cadr pt-model))
;; 	     (princ (vla:get-value mvalues))
;; 	     (vla-setxdata obj-pv
;; 			   mtypes
;; 			   mvalues)
;; 	     (vla-update obj-pv)
;; 	     (vla-display obj-pv :vlax-true)
;; 	     )
;;       ))

;; (entmakex (list (quote (0 . "viewport"))
;;         (quote (100 . "acdbentity"))
;;         (quote (67 . 1))
;;         (cons 410 layout)
;;         (quote (100 . "acdbviewport"))
;;         (cons 10 pt-center)
;;         (cons 40 width)
;;         (cons 41 height)
;;         (quote (68 . 2))
;;         (quote (69 . 2))
;;         (cons 12 pt-model)
;;         (quote (13 0.0 0.0 0.0))
;;         (quote (14 0.5 0.5 0.0))
;;         (quote (15 0.5 0.5 0.0))
;;         (quote (16 0.0 0.0 1.0))
;;         (quote (17 6.0 4.5 -6.89434))
;;         (quote (42 . 50.0))
;;         (quote (43 . 0.0))
;;         (quote (44 . 0.0))
;;         (quote (45 . 1.79005e+006))
;;         (quote (50 . 0.0))
;;         (quote (51 . 0.0))
;;         (quote (72 . 1))
;;         (quote (90 . 819296))
;;         (quote (281 . 0))
;;         (quote (71 . 1))
;;         (quote (74 . 0))
;;         (quote (110 0.0 0.0 0.0))
;;         (quote (111 1.0 0.0 0.0))
;;         (quote (112 0.0 1.0 0.0))
;;         (quote (79 . 0))
;;         (quote (146 . 0.0))
;;         (quote (170 . 0))
;;         (quote (61 . 5))
;;         (quote (292 . 1))
;;         (quote (282 . 1))
;;         (quote (141 . 0.0))
;;         (quote (142 . 0.0))
;;         (quote (63 . 250)))))
