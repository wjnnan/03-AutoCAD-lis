(defun std:insertpopmenuitems (popupmenu popitems / k tmp)
    (setq k 0)
    (mapcar (function (lambda (x / label cmdstr hlpstr subitems tmp)
                (setq label (car x)
                    cmdstr (cadr x)
                    hlpstr (caddr x)
                    subitems (cadddr x))
                (if (= label "--")
                    (vla-addseparator popupmenu (setq k (1+ k)))
                    (if (and label cmdstr)
                        (progn (setq tmp (vla-addmenuitem popupmenu (setq k (1+ k))
                                    label cmdstr))
                            (vla-put-helpstring tmp hlpstr))
                        (progn (setq tmp (vla-addsubmenu popupmenu (setq k (1+ k))
                                    label))
                            (if subitems (std:insertpopmenuitems tmp subitems)))))))
        popitems))
