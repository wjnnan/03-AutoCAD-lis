(defun file:list-to-stream (out_file intlist / adodb)
    (setq intlist (vlax-make-variant (vlax-safearray-fill (vlax-make-safearray 17 (cons 0 (1- (length intlist))))
                intlist)
            8209))
    (setq adodb (vlax-get-or-create-object "adodb.stream"))
    (vlax-put-property adodb (quote type)
        1)
    (vlax-invoke adodb (quote open))
    (vlax-put adodb (quote position)
        0)
    (vlax-invoke-method adodb (quote write)
        intlist)
    (vlax-invoke adodb (quote savetofile)
        out_file 2)
    (and adodb (vlax-invoke adodb (quote close)))
    (and adodb (vlax-release-object adodb))
    (princ))
