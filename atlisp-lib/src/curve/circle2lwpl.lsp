(defun curve:circle2lwpl (ent-circle int / pt-center r pts bulge convexity ent i)
  "将圆转换成 由 int 段组成的多段线。"
  "多段线图元"
  (setq int (fix int))
  (if (< (fix int) 2)(setq int 2))
  (setq pt-center (entity:getdxf ent-circle 10)
    r (entity:getdxf ent-circle 40))
  (setq pts (quote nil))
  (setq bulge (curve:o2bulge (polar pt-center 0 r)
      (polar pt-center (/ (* 2 pi)
          int)
        r)
      pt-center))
  (setq i 0)
  (repeat int (setq pts (cons (polar pt-center (* i (/ (* 2 pi)
              int))
          r)
        pts))
    (setq i (1+ i))
    (setq convexity (cons (- bulge)
        convexity)))
  (push-var)
  (setvar "osmode"
    0)
  (setq ent (entity:putdxf (entity:putdxf (entity:make-lwpline-bold pts convexity nil 1 0)
        8 (entity:getdxf ent-circle 8))
      62 (if (entity:getdxf ent-circle 62)
        (entity:getdxf ent-circle 62)
        256)))
  (pop-var)
  ent)
