(defun base64:encode (lst-uint8 / i res lst-str rem%)
  "将字节列表内容转为 base64 编码。"
  "String"
  (if (and (listp lst-uint8)
      (apply (quote and)
        (mapcar (quote numberp)
          lst-uint8)))
    (progn (setq lst-base64 (vl-string->list "ABCDEFGHIJKLMNOPQRSTUVWXYZabcdefghijklmnopqrstuvwxyz0123456789+/"))
      (setq i 0)
      (setq res (quote nil))
      (setq rem% 0)
      (foreach b lst-uint8 (cond ((= i 0)
            (setq res (cons (/ b 4)
                res))
            (setq rem% (logand b 3))
            (setq i 1))
          ((= i 1)
            (setq res (cons (+ (lsh rem% 4)
                  (/ b 16))
                res))
            (setq rem% (logand b 15))
            (setq i 2))
          ((= i 2)
            (setq res (cons (+ (lsh rem% 2)
                  (/ b 64))
                res))
            (setq res (cons (logand b 63)
                res))
            (setq rem% 0)
            (setq i 0))))
      (cond ((= i 1)
          (setq res (cons (lsh rem% 4)
              res)))
        ((= i 2)
          (setq res (cons (lsh rem% 2)
              res))))
      (setq res (mapcar (quote (lambda (x)
              (nth x lst-base64)))
          res))
      (if (/= i 0)
        (repeat (- 3 i)
          (setq res (cons (ascii "=")
              res))))
      (vl-list->string (reverse res)))))
