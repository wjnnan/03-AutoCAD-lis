(defun base64:base64-to-file (file str-base64 / xmldom node stream)
  (if is-gcad (progn (princ "This function CAN NOT support GstarCAD.")
      nil)
    (progn (setq xmldom (vlax-get-or-create-object "MSXML2.DOMDocument"))
      (setq node (vlax-invoke-method xmldom (quote createelement)
          "binary"))
      (vlax-put-property node (quote datatype)
        "bin.base64")
      (vlax-put-property node (quote text)
        str-base64)
      (setq stream (vlax-get-or-create-object "ADODB.Stream"))
      (vlax-put-property stream (quote type)
        1)
      (vlax-invoke stream (quote open))
      (vlax-invoke-method stream (quote write)
        (vlax-get-property node (quote nodetypedvalue)))
      (vlax-invoke-method stream (quote savetofile)
        file 2)
      (vlax-invoke stream (quote close))
      (vlax-release-object stream)
      (vlax-release-object node)
      (vlax-release-object xmldom)
      t)))
