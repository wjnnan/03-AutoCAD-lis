;; @param blk 块图元
(defun block:get-effectivename (blkref / tem blkname *error*)
  "取得块真实名称，支持 MAC"
  (defun *error* (msg)
    (princ "图块定义异常")
    "")
  (cond ((and (= (quote ename)
		 (type blkref))
	      (entget blkref))
	 (progn (setq blkname (cdr (assoc 2 (entget blkref))))
		(if (wcmatch blkname "`**")
		    (if (and (setq tem (cdadr (assoc -3 (entget (cdr (assoc 330 (entget (tblobjname "block"
												    blkname))))
								(quote ("AcDbBlockRepBTag"))))))
			     (setq tem (handent (cdr (assoc 1005 tem)))))
			(setq blkname (cdr (assoc 2 (entget tem))))))
		blkname))
	((= (quote vla-object)
	    (type blkref))
	 (if (vl-catch-all-error-p
	       (setq tem (vl-catch-all-apply 'vla-get-effectivename (list blkref))))
	     (vl-catch-all-apply 'vla-get-name (list blkref))
	   tem))
	(t "")))
