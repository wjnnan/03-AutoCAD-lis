(defun vectra:setvars (pairs / changed name old value)
  (if (atom (car pairs))
    (setq pairs (list pairs)))
  (foreach pair pairs (setq name (car pair)
      value (cdr pair)
      old (getvar name))
    (if old (progn (setq changed (cons (cons name old)
            changed))
        (setvar name value))))
  (reverse changed))
