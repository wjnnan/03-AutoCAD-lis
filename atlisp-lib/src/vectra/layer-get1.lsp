(defun vectra:layer-get1 (name dxf / r)
  (setq r (tblsearch "LAYER"
      name))
  (if (null r)
    (setq r (entmake (vectra:set (list (quote (0 . "LAYER"))
            (quote (100 . "AcDbSymbolTableRecord"))
            (quote (100 . "AcDbLayerTableRecord"))
            (quote (70 . 0))
            (quote (6 . "Continuous"))
            (quote (62 . 7))
            (quote (370 . -3))
            (cons 2 name))
          dxf))))
  r)
