(defun vectra:regexp-match (str pattern / matchs reg r)
  (setq reg (vlax-create-object "vbscript.regexp"))
  (vlax-put-property reg (quote global)
    1)
  (vlax-put-property reg (quote ignorecase)
    1)
  (vlax-put-property reg (quote pattern)
    pattern)
  (setq matchs (vlax-invoke reg (quote execute)
      str))
  (vlax-for k matchs (setq r (cons (vlax-get k (quote value))
        r)))
  (vlax-release-object reg)
  (reverse r))
