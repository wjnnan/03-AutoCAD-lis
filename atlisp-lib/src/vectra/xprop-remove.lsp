(defun vectra:xprop-remove (ename appname names / xdata xdata2)
  (if (and names (atom names))
    (setq names (list names)))
  (if names (progn (setq xdata (vectra:xdata-get ename appname))
      (while xdata (if (member (cdar xdata)
            names)
          (setq names (vl-remove (cdar xdata)
              names))
          (setq xdata2 (cons (car xdata)
              xdata2)
            xdata2 (cons (cadr xdata)
              xdata2)))
        (setq xdata (cddr xdata)))
      (setq xdata2 (reverse xdata2))
      (vectra:xdata-set ename appname xdata2))))
