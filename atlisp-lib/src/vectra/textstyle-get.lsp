(defun vectra:textstyle-get (name font bigfont width / style styles)
  (setq styles (vla-get-textstyles (vla-get-activedocument (vlax-get-acad-object))))
  (if (vl-catch-all-error-p (setq style (vl-catch-all-apply (quote vla-item)
          (list styles name))))
    (progn (setq style (vla-add styles name))
      (vla-put-fontfile style font)
      (vla-put-bigfontfile style bigfont)
      (vla-put-width style width)))
  style)
