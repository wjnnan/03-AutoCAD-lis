(defun vectra:refgeom (ename / elst ang norm mat)
  (setq elst (entget ename)
    ang (cdr (assoc 50 elst))
    norm (cdr (assoc 210 elst)))
  (list (setq mat (vectra:mxm (mapcar (function (lambda (v)
              (trans v 0 norm t)))
          (quote ((1.0 0.0 0.0)
              (0.0 1.0 0.0)
              (0.0 0.0 1.0))))
        (vectra:mxm (list (list (cos ang)
              (- (sin ang))
              0.0)
            (list (sin ang)
              (cos ang)
              0.0)
            (quote (0.0 0.0 1.0)))
          (list (list (cdr (assoc 41 elst))
              0.0 0.0)
            (list 0.0 (cdr (assoc 42 elst))
              0.0)
            (list 0.0 0.0 (cdr (assoc 43 elst)))))))
    (mapcar (quote -)
      (trans (cdr (assoc 10 elst))
        norm 0)
      (vectra:mxv mat (cdr (assoc 10 (tblsearch "BLOCK"
              (cdr (assoc 2 elst)))))))))
