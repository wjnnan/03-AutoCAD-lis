(defun vectra:csvfile-readcache (filename cache / data)
  (if (and (setq filename (findfile filename))
      (setq filename (strcase filename))
      (null (setq data (vectra:get (vl-symbol-value cache)
            filename))))
    (progn (setq data (vectra:csvfile-read filename))
      (set cache (cons (cons filename data)
          (vl-symbol-value cache)))))
  data)
