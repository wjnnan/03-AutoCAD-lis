(setq *log* (open "d:/My Code/Claude Code/03-AutoCAD-lisp/_ext_result.log" "w"))
(setq *ok* 0 *bad* 0)
(defun lg (m) (write-line m *log*) (princ (strcat "\n" m)))
(defun try (label path)
  (lg (strcat "LOAD " label))
  (if (not (findfile path))
    (progn (lg "  SKIP not found") nil)
    (if (vl-catch-all-error-p (setq r (vl-catch-all-apply 'load (list path))))
      (progn (lg (strcat "  FAIL: " (vl-catch-all-error-message r)))
             (setq *bad* (1+ *bad*)) nil)
      (progn (lg "  OK") (setq *ok* (1+ *ok*)) T))))

(lg "===== 1. pipe-router-autolisp =====")
(try "pipedraw.lsp" "d:/My Code/Claude Code/03-AutoCAD-lisp/_tmp_pipe-router-autolisp/pipedraw.lsp")

(lg "===== 2. AutoCAD-LISP tools =====")
(try "Multiple Offset" "d:/My Code/Claude Code/03-AutoCAD-lisp/_tmp_AutoCAD-LISP/1- Multiple offset/Multiple Offset.lsp")
(try "Match Block Orientation" "d:/My Code/Claude Code/03-AutoCAD-lisp/_tmp_AutoCAD-LISP/3- Match Block orientation/Match Block Orientation.lsp")
(try "replace blocks" "d:/My Code/Claude Code/03-AutoCAD-lisp/_tmp_AutoCAD-LISP/4- Replace block/replace blocks.lsp")
(try "Round Attributes Text" "d:/My Code/Claude Code/03-AutoCAD-lisp/_tmp_AutoCAD-LISP/5- Round Block Attributes/1/ROUND ATTRIBUTES TEXT 1.0.LSP")

(lg "===== 3. cathedral lib =====")
(try "core.LSP" "d:/My Code/Claude Code/03-AutoCAD-lisp/_tmp_cathedral/src/core/core.LSP")
(try "math.LSP" "d:/My Code/Claude Code/03-AutoCAD-lisp/_tmp_cathedral/src/math/math.LSP")
(try "block.LSP" "d:/My Code/Claude Code/03-AutoCAD-lisp/_tmp_cathedral/src/block/block.LSP")
(try "string.LSP" "d:/My Code/Claude Code/03-AutoCAD-lisp/_tmp_cathedral/src/string/string.LSP")
(try "association-list.LSP" "d:/My Code/Claude Code/03-AutoCAD-lisp/_tmp_cathedral/src/list/association-list.LSP")
(try "excell-files.LSP" "d:/My Code/Claude Code/03-AutoCAD-lisp/_tmp_cathedral/src/files/excell-files.LSP")
(try "simple-list.lsp" "d:/My Code/Claude Code/03-AutoCAD-lisp/_tmp_cathedral/src/list/simple-list.lsp")
(try "date-time.lsp" "d:/My Code/Claude Code/03-AutoCAD-lisp/_tmp_cathedral/src/core/date-time.lsp")

(lg "===== SUMMARY =====")
(lg (strcat "PASS=" (itoa *ok*) " FAIL=" (itoa *bad*)))
(close *log*)
(princ)
