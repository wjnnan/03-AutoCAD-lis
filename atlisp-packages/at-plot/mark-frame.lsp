(@:add-menu "通用打印" "标记图框" "(@plot:mark-frames)")
(defun @plot:mark-frames (/ tks)
  (@plot:init)
  
  (foreach frame-pts @plot:*frames*
	   ;; (print (cdr frame-pts))
	   (@plot:draw-frame
	    (vl-sort (car frame-pts)
		     '(lambda (pt1 pt2)
			(or (< (car pt1)(car pt2))
			    (and (equal (car pt1)(car pt2) 0.001)
				 (< (cadr pt1)(cadr pt2))))))
	    (cdr frame-pts)
	    300)
	   )
  (setq tks (ssget "x" '((8 . "temp-frames"))))
  (setvar "cmdecho"  0)
  (if (/= nil tks)
      (command  "_.draworder" tks "" "F")
      )
  (setvar "cmdecho" 1)
  (princ)
  )

(@:add-menu "通用打印" "删图框标记" "(@plot:delete-mark)")
(defun @plot:delete-mark (/ tf)
  (@plot:init)
  (if (setq tf (ssget "x" '((0 . "LWPOLYLINE")
			    (90 . 4)(70 . 1)
			    (8 . "temp-frames"))))
      (pickset:erase tf))
  (setq @plot:*frames* '())
  (princ)
  )
(defun @plot:draw-frame (plist layout% bold / lst-dxf)
  (setq lst-dxf
	(list '(0 . "LWPOLYLINE")
	      '(100 . "AcDbEntity")
	      '(62 . 1)
	      (cons 410 layout%)
	      '(370 . 30)
	      '(8 . "temp-frames")
	      '(100 . "AcDbPolyline")
	      (cons 90 (length plist))
	      '(70 . 1)
	      (cons 43 bold)
	      '(38 . 0.0)
	      '(39 . 0.0)))
  
  (foreach x plist
	   (setq lst-dxf (append lst-dxf 
				 (list (cons 10 x)
				       (cons 40 bold)
				       (cons 41 bold)
				       (cons 42 0)
				       (cons 91 0)
				       ))))
  (entmake lst-dxf)
  (entlast)
  )
