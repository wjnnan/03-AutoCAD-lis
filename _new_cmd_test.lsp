(setvar "SECURELOAD" 0)
(setq *log* (open "d:/My Code/Claude Code/03-AutoCAD-lisp/_new_cmd_result.log" "w"))
(setq *ok* 0 *bad* 0)
(defun lg (m) (write-line m *log*) (princ (strcat "
" m)))
(defun ck (name)
  (if (uc:function-defined-p (read name))
    (progn (lg (strcat "  OK   " name)) (setq *ok* (1+ *ok*)))
    (progn (lg (strcat "  FAIL " name)) (setq *bad* (1+ *bad*)))))
(lg "===== Loading TB-Toolbox =====")
(setq *TB:PATH* "d:/My Code/Claude Code/03-AutoCAD-lisp/TB-Toolbox")
(if (vl-catch-all-error-p (setq r (vl-catch-all-apply 'load (list (strcat *TB:PATH* "/load.lsp")))))
  (lg (strcat "LOAD FAIL: " (vl-catch-all-error-message r)))
  (progn
    (lg "Toolbox loaded")
    (lg "")
    (lg "===== 1. from AutoCAD-LISP: offset =====")
    (ck "c:MOF")
    (lg "")
    (lg "===== 2. from AutoCAD-LISP: block tools =====")
    (ck "c:MBO") (ck "c:RAV") (ck "c:RBLK")
    (lg "")
    (lg "===== 3. previously absorbed =====")
    (ck "c:FCK") (ck "c:SEIS") (ck "c:SECT") (ck "c:GJZL")
    (ck "c:SSC") (ck "c:SSM") (ck "c:HOLE") (ck "c:BOFF")
    (lg "")
    (lg (strcat "Catalog size: " (itoa (length *TB:CMD-CATALOG*))))))
(lg "")
(lg "===== SUMMARY =====")
(lg (strcat "PASS=" (itoa *ok*) " FAIL=" (itoa *bad*)))
(close *log*)
(princ)
